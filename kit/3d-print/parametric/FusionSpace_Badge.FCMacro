# FusionSpace badge: a parametric template for FreeCAD (0.21 and 1.x).
# Macro > Macros... > select this file > Execute. It makes a new document with a spreadsheet "Params"; change a value
# there and recompute (Ctrl+R): the badge follows. Export "Badge" (no pocket) or "BadgeMagnet" with File > Export.
# Generated by tools/build/kit_cad.py from the master geometry: the mark is exact (lines, circular arcs, the elliptical
# wing's ellipse and the Von Karman's Bezier curves), 50 mm tall here, feet cut at 0.6 mm, and scaled from Params.
import FreeCAD as App
import Part

MARK = [["main", [["bezier", [24.9565495784, 24.9388749533], [24.9863181866, 24.9091063451], [25.0084568982, 24.7571243534], [25.0145481073, 24.638904581]], ["bezier", [25.0145481073, 24.638904581], [25.0354471054, 24.2332913834], [24.9480839041, 23.673517959], [24.8571308806, 23.2235048259]], ["bezier", [24.8571308806, 23.2235048259], [24.595953271, 21.9312624152], [24.1218399776, 20.4969863305], [23.5800341705, 19.0562350605]], ["bezier", [23.5800341705, 19.0562350605], [22.4711706918, 16.1075836356], [20.9742084277, 12.9058692504], [19.1967290804, 9.5261591576]], ["bezier", [19.1967290804, 9.5261591576], [15.13058449, 1.7947669856], [10.1195799397, -5.6715420327], [6.4727204642, -10.3202695457]], ["line", [6.4727204642, -10.3202695457], [6.0406278867, -9.8881769683]], ["arc", [6.0406278867, -9.8881769683], [3.3519207073, 3.3342460822], [-9.8705023431, 6.0229532616]], ["line", [-9.8705023431, 6.0229532616], [-10.3025949206, 6.455045839]], ["bezier", [-10.3025949206, 6.455045839], [-5.6538674075, 10.1019053145], [1.8124416108, 15.1129098649], [9.5438337827, 19.1790544553]], ["bezier", [9.5438337827, 19.1790544553], [12.9235438756, 20.9565338025], [16.1252582607, 22.4534960666], [19.0739096857, 23.5623595453]], ["bezier", [19.0739096857, 23.5623595453], [20.5146609556, 24.1041653525], [21.9489370404, 24.5782786458], [23.2411794511, 24.8394562554]], ["bezier", [23.2411794511, 24.8394562554], [23.6911925842, 24.9304092789], [24.2509660085, 25.0177724803], [24.6565792062, 24.9968734822]], ["bezier", [24.6565792062, 24.9968734822], [24.7747989786, 24.9907822731], [24.9267809702, 24.9686435614], [24.9565495784, 24.9388749533]]]], ["west", [["line", [-12.7875218111, 12.8988970319], [-19.5820511331, 0.6687442524]], ["line", [-19.5820511331, 0.6687442524], [-20.0063152018, 1.0930083211]], ["arc", [-20.0063152018, 1.0930083211], [-21.4293733596, 4.2570454835], [-24.5934105219, 5.6801036413]], ["line", [-24.5934105219, 5.6801036413], [-25.0176745906, 6.10436771]], ["line", [-25.0176745906, 6.10436771], [-12.7875218111, 12.8988970319]]]], ["east", [["ellipse", [11.0907835815, -14.8401514287], [10.6119750985, -18.6747815468], [6.0473369751, -24.999999988], [2.0168394557, -23.9140955546], [-0.7071067812, -0.7071067812], 12.832494847, 3.6664270991], ["line", [6.0473369751, -24.999999988], [5.6230729064, -24.5757359193]], ["arc", [5.6230729064, -24.5757359193], [4.6093949202, -21.32154009], [1.355199091, -20.3078621038]], ["line", [1.355199091, -20.3078621038], [0.9309350222, -19.8835980351]], ["ellipse", [0.9309350222, -19.8835980351], [7.2561534635, -15.3189599118], [11.0907835815, -14.8401514287], [2.0168394557, -23.9140955546], [-0.7071067812, -0.7071067812], 12.832494847, 3.6664270991]]], ["south", [["arc", [-3.7297260534, -3.7474006785], [-7.1011818613, -12.9720720643], [-12.5948416449, -21.1133851416]], ["line", [-12.5948416449, -21.1133851416], [-13.0191057136, -20.6891210728]], ["arc", [-13.0191057136, -20.6891210728], [-14.5320404889, -14.5497151141], [-20.6714464477, -13.0367803388]], ["line", [-20.6714464477, -13.0367803388], [-21.0957105164, -12.6125162701]], ["arc", [-21.0957105164, -12.6125162701], [-12.9543974391, -7.1188564865], [-3.7297260534, -3.7474006785]]]]]
REF = 50.0          # mm: the height MARK is drawn at
POCKET = (-0.08933, -0.07344)     # magnet pocket center, x and y as a fraction of the mark height (the base's thickest point)
REACH = 0.70563          # the mark's farthest point from its center, as a fraction of its height
PARAMS = [  # alias, value (mm), note
    ("MarkHeight", 40, "mark height, mm (the name is not in this template)"),
    ("Margin", 3, "clear plate around the mark's farthest point (the main cone's tip), mm"),
    ("PlateDiameter", "=2 * MarkHeight * REACH + 2 * Margin", "round plate diameter, mm: follows the mark and the margin (type a number to fix it)"),
    ("PlateThickness", 4.0, "plate thickness, mm (keep it in 0.2 mm layers)"),
    ("Relief", 1.2, "cones raised by, mm"),
    ("MagnetDiameter", 10.3, "pocket diameter, mm: magnet + 0.3"),
    ("MagnetDepth", 3.2, "pocket depth from the back, mm: magnet + 0.2; leave 0.8 mm above it"),
]

def V(p): return App.Vector(p[0], p[1], 0)

def edge(c):
    k = c[0]
    if k == "line": return Part.LineSegment(V(c[1]), V(c[2])).toShape()
    if k == "arc": return Part.Arc(V(c[1]), V(c[2]), V(c[3])).toShape()
    if k == "bezier":
        b = Part.BezierCurve(); b.setPoles([V(p) for p in c[1:]]); return b.toShape()
    _, p0, pm, p1, cen, d, a, b = c          # ellipse arc: center, major-axis direction, semi-axes
    import math
    el = Part.Ellipse(V((cen[0] + d[0] * a, cen[1] + d[1] * a)), V((cen[0] - d[1] * b, cen[1] + d[0] * b)), V(cen))
    def par(p):
        return el.parameter(V(p))
    u0, um, u1 = par(p0), par(pm), par(p1)
    two = 2 * math.pi
    if (um - u0) % two < (u1 - u0) % two: s, e = u0, u0 + (u1 - u0) % two
    else: s, e = u1, u1 + (u0 - u1) % two
    return Part.ArcOfEllipse(el, s, e).toShape()

def mark_shape():
    faces = []
    for name, curves in MARK:
        w = Part.Wire(Part.__sortEdges__([edge(c) for c in curves]))
        f = Part.Face(w)
        if not f.isValid(): f.fix(1e-6, 1e-6, 1e-6)
        faces.append(f)
    return Part.makeCompound(faces)

doc = App.newDocument("FusionSpaceBadge")
sheet = doc.addObject("Spreadsheet::Sheet", "Params")
for i, (alias, val, note) in enumerate(PARAMS, start=1):
    sheet.set(f"A{i}", alias); sheet.set(f"C{i}", note); sheet.setAlias(f"B{i}", alias)
for i, (alias, val, note) in enumerate(PARAMS, start=1):
    sheet.set(f"B{i}", str(val).replace("REACH", str(REACH)))
doc.recompute()

ref = doc.addObject("Part::Feature", "MarkReference"); ref.Shape = mark_shape(); ref.Label = "Mark (reference, %g mm)" % REF
try:
    import Draft
    mark = Draft.make_clone(ref) if hasattr(Draft, "make_clone") else Draft.clone(ref)
except Exception:
    mark = doc.addObject("Part::FeaturePython", "Mark")
mark.Label = "Mark"
for ax in ("x", "y"): mark.setExpression(f"Scale.{ax}", f"Params.MarkHeight / {REF}")
mark.setExpression(".Placement.Base.z", "Params.PlateThickness")
relief = doc.addObject("Part::Extrusion", "Relief")
relief.Base = mark; relief.DirMode = "Custom"; relief.Dir = App.Vector(0, 0, 1); relief.Solid = True
relief.setExpression("LengthFwd", "Params.Relief")
plate = doc.addObject("Part::Cylinder", "Plate")
plate.setExpression("Radius", "Params.PlateDiameter / 2"); plate.setExpression("Height", "Params.PlateThickness")
badge = doc.addObject("Part::MultiFuse", "Badge"); badge.Shapes = [plate, relief]
pocket = doc.addObject("Part::Cylinder", "Pocket")
pocket.setExpression("Radius", "Params.MagnetDiameter / 2"); pocket.setExpression("Height", "Params.MagnetDepth")
pocket.setExpression(".Placement.Base.x", f"Params.MarkHeight * {POCKET[0]}")
pocket.setExpression(".Placement.Base.y", f"Params.MarkHeight * {POCKET[1]}")
withmag = doc.addObject("Part::Cut", "BadgeMagnet"); withmag.Base = badge; withmag.Tool = pocket
for o in (ref, mark, relief, plate, pocket, badge):
    try: o.Visibility = False
    except Exception: pass
doc.recompute()
try:
    import FreeCADGui as Gui
    Gui.SendMsgToActiveView("ViewFit"); Gui.activeDocument().activeView().viewIsometric()
except Exception:
    pass
